module test {
  namespace "https://github.com/alliedtelesis/apteryx";
  prefix test;

  organization
    "The organization name";

  revision 2018-02-20 {
    description
      "Original version";
  }

  container test {
    description "This is a test node";
    container settings {
      description "Settings";
      leaf debug {
        description "Debug configuration";
        default "disable";
        type enumeration {
          enum disable {
            value 0;
            description "Debugging is disabled";
          }
          enum enable {
            value 1;
            description "Debugging is enabled";
          }
        }
      }
      leaf enable {
        type boolean;
        default "false";
        description "boolean";
      }
      leaf priority {
        type uint32;
        description "integer";
      }
    }
    container state {
      description "State";
      config false;
      leaf counter {
        type uint32;
        default "0";
        description "uint32";
      }
    }
    container animals {
      list animal {
        key "name";
        description "This is a list of animals";
        leaf name {
          description "This is the name of the animal";
          type string;
        }
        leaf type {
          description "This is the type of the animal";
          default "big";
          type enumeration {
            enum big {
              value 1;
            }
            enum little {
              value 2;
            }
          }
        }
        leaf colour {
          description "This is the colour of the animal";
          type string;
        }
      }
      container toys {
        leaf-list toy {
          description "This is a simple list of toys";
          type string;
        }
      }
    }
  }
}
